(command "3dface"  "2,2,0.1" "2,1,0.1" "1,1,0.2" "2,2,0.1" "")
(command "3dface"  "1,1,0.2" "1,2,0.2" "2,2,0.1" "1,1,0.2" "")
(command "3dface"  "2,1,0.1" "2,0,0.1" "1,1,0.2" "2,1,0.1" "")
(command "3dface"  "1,2,0.2" "2,3,0.1" "2,2,0.1" "1,2,0.2" "")
(command "3dface"  "1,2,0.2" "1,3,0.2" "2,3,0.1" "1,2,0.2" "")
(command "3dface"  "1,0,0.2" "0,1,0" "1,1,0.2" "1,0,0.2" "")
(command "3dface"  "1,1,0.2" "0,1,0" "1,2,0.2" "1,1,0.2" "")
(command "3dface"  "1,2,0.2" "0,2,0" "1,3,0.2" "1,2,0.2" "")
(command "3dface"  "2,2,0.1" "3,1,-0.1" "2,1,0.1" "2,2,0.1" "")
(command "3dface"  "2,1,0.1" "3,1,-0.1" "2,0,0.1" "2,1,0.1" "")
(command "3dface"  "3,2,-0.1" "3,1,-0.1" "2,2,0.1" "3,2,-0.1" "")
(command "3dface"  "2,0,0.1" "1,0,0.2" "1,1,0.2" "2,0,0.1" "")
(command "3dface"  "0,1,0" "0,2,0" "1,2,0.2" "0,1,0" "")
(command "3dface"  "2,3,0.1" "3,2,-0.1" "2,2,0.1" "2,3,0.1" "")
(command "3dface"  "2,3,0.1" "3,3,-0.1" "3,2,-0.1" "2,3,0.1" "")
(command "3dface"  "0,2,0" "0,3,0" "1,3,0.2" "0,2,0" "")
(command "3dface"  "1,0,0.2" "0,0,0" "0,1,0" "1,0,0.2" "")
(command "3dface"  "3,1,-0.1" "3,0,-0.1" "2,0,0.1" "3,1,-0.1" "")
(command "3dface"  "3,3,-0.1" "4,2,-0.4" "3,2,-0.1" "3,3,-0.1" "")
(command "3dface"  "3,2,-0.1" "4,2,-0.4" "3,1,-0.1" "3,2,-0.1" "")
(command "3dface"  "3,1,-0.1" "4,1,0" "3,0,-0.1" "3,1,-0.1" "")
(command "3dface"  "4,2,-0.4" "4,1,0" "3,1,-0.1" "4,2,-0.4" "")
(command "3dface"  "1,3,0.2" "1,4,0.2" "2,3,0.1" "1,3,0.2" "")
(command "3dface"  "2,3,0.1" "2,4,0.1" "3,3,-0.1" "2,3,0.1" "")
(command "3dface"  "0,3,0" "1,4,0.2" "1,3,0.2" "0,3,0" "")
(command "3dface"  "1,4,0.2" "2,4,0.1" "2,3,0.1" "1,4,0.2" "")
(command "3dface"  "3,3,-0.1" "4,3,-0.6" "4,2,-0.4" "3,3,-0.1" "")
(command "3dface"  "2,4,0.1" "3,4,-0.1" "3,3,-0.1" "2,4,0.1" "")
(command "3dface"  "4,1,0" "4,0,0" "3,0,-0.1" "4,1,0" "")
(command "3dface"  "3,4,-0.1" "4,3,-0.6" "3,3,-0.1" "3,4,-0.1" "")
(command "3dface"  "0,3,0" "0,4,0" "1,4,0.2" "0,3,0" "")
(command "3dface"  "1,4,0.2" "1,5,0.2" "2,4,0.1" "1,4,0.2" "")
(command "3dface"  "2,4,0.1" "2,5,-0.3" "3,4,-0.1" "2,4,0.1" "")
(command "3dface"  "0,4,0" "1,5,0.2" "1,4,0.2" "0,4,0" "")
(command "3dface"  "1,5,0.2" "2,5,-0.3" "2,4,0.1" "1,5,0.2" "")
(command "3dface"  "3,5,-0.1" "4,4,0" "3,4,-0.1" "3,5,-0.1" "")
(command "3dface"  "3,4,-0.1" "4,4,0" "4,3,-0.6" "3,4,-0.1" "")
(command "3dface"  "5,3,-0.2" "5,2,-0.15" "4,3,-0.6" "5,3,-0.2" "")
(command "3dface"  "4,3,-0.6" "5,2,-0.15" "4,2,-0.4" "4,3,-0.6" "")
(command "3dface"  "4,2,-0.4" "5,2,-0.15" "4,1,0" "4,2,-0.4" "")
(command "3dface"  "4,1,0" "5,1,0" "4,0,0" "4,1,0" "")
(command "3dface"  "5,2,-0.15" "5,1,0" "4,1,0" "5,2,-0.15" "")
(command "3dface"  "4,4,0" "5,3,-0.2" "4,3,-0.6" "4,4,0" "")
(command "3dface"  "0,4,0" "0,5,0" "1,5,0.2" "0,4,0" "")
(command "3dface"  "5,1,0" "5,0,0" "4,0,0" "5,1,0" "")
(command "3dface"  "2,5,-0.3" "3,5,-0.1" "3,4,-0.1" "2,5,-0.3" "")
(command "3dface"  "4,5,0" "5,4,0" "4,4,0" "4,5,0" "")
(command "3dface"  "4,4,0" "5,4,0" "5,3,-0.2" "4,4,0" "")
(command "3dface"  "3,5,-0.1" "4,5,0" "4,4,0" "3,5,-0.1" "")
(command "3dface"  "4,5,0" "5,5,0" "5,4,0" "4,5,0" "")
